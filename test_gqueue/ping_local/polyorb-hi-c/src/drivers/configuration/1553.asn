POHICDRIVER-1553 DEFINITIONS AUTOMATIC TAGS ::= BEGIN

Node-Addr-T ::= INTEGER (0 .. 31) 

Standard-T  ::= ENUMERATED {mil1553a, mil1553b}

Mode-T  ::= ENUMERATED {controller, terminal, monitor}

Bus-T  ::= ENUMERATED {none, bus-a, bus-b, both}

Mil-1553-Conf-T ::= SEQUENCE {
   devname        IA5String (SIZE (1..20)),
	standard		   Standard-T,
	mode			   Mode-T,
	bus			   Bus-T,
	termaddr			Node-Addr-T,
	broadcast		BOOLEAN,
	rxblock			BOOLEAN OPTIONAL,
	txblock			BOOLEAN OPTIONAL
}


END
