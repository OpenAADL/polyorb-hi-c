POHICDRIVER-SPACEWIRE DEFINITIONS AUTOMATIC TAGS ::= BEGIN

Core-Frequence-T ::= INTEGER (0 .. 4294967295)

Node-Addr-T ::= INTEGER (0 .. 255)

Clock-Division-T ::= INTEGER (0 .. 255)

Spacewire-Conf-T ::= SEQUENCE {
   devname        IA5String (SIZE (1..20)),
	nodeaddr			Node-Addr-T,
	corefreq			Core-Frequence-T OPTIONAL,
	clockdiv			Clock-Division-T OPTIONAL,
	use-router		BOOLEAN DEFAULT FALSE,
	remove-prot-id	BOOLEAN OPTIONAL,
	rxblock			BOOLEAN OPTIONAL,
	txblock			BOOLEAN OPTIONAL
}


leon-rasta-spw-sender Spacewire-Conf-T ::= {
   devname     "/dev/grspwrasta0",
   nodeaddr    11
}

leon-rasta-spw-receiver Spacewire-Conf-T ::= {
   devname     "/dev/grspwrasta0",
   nodeaddr    22
}




END
