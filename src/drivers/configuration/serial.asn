POHICDRIVER-UART DEFINITIONS AUTOMATIC TAGS ::= BEGIN

Baudrate-T  ::= ENUMERATED
                  {b9600,
                   b19200,
                   b38400,
                   b57600,
                   b115200,
                   b230400}

Parity-T    ::= ENUMERATED {even, odd}

Serial-Conf-T ::= SEQUENCE {
   devname        IA5String (SIZE (1..20)),
   speed          Baudrate-T OPTIONAL,
   parity         Parity-T OPTIONAL,
   bits           INTEGER (7 .. 8) OPTIONAL,
   sending-wait   INTEGER (0 .. 9000000) OPTIONAL,
   use-paritybit  BOOLEAN  OPTIONAL
}

linux-ttyS0 Serial-Conf-T ::= {
   devname     "/dev/ttyS0",
   speed       b38400
}


linux-ttyUSB0 Serial-Conf-T ::= {
   devname     "/dev/ttyUSB0",
   speed       b38400
}


linux-ttyUSB1 Serial-Conf-T ::= {
   devname     "/dev/ttyUSB1",
   speed       b38400
}


linux-ttyUSB2 Serial-Conf-T ::= {
   devname     "/dev/ttyUSB2",
   speed       b38400
}


leon-rasta-apburasta0 Serial-Conf-T ::= {
   devname     "/dev/apburasta0",
   speed       b38400
}

leon-rasta-apburasta1 Serial-Conf-T ::= {
   devname     "/dev/apburasta1",
   speed       b38400
}


END
